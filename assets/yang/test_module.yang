module test_module {
    namespace "urn:test_module";
    prefix tm;

    leaf testInt32 {
        type int32;
    }

    leaf stateLeaf {
        config false;
        type int32;
    }

    leaf-list values {
        ordered-by user;
        type int32;
    }

    leaf leafWithDefault {
        type int32;
        default 123;
    }



    container cont {
        presence true;
        leaf l {
            type string{
                length "0..10";
            }
        }



        container sub {

            list test-list {
                key name;
                leaf name {
                    type string;
                }
                leaf val {
                    type string;
                }

                container cont {
                    leaf l {
                        type string;
                    }
                }

            }

        }

    }

    container stats {
        config false;
        leaf counter {
            type uint64;
        }

        leaf counter2 {
            type uint64;
        }
    }

    rpc oper {
        input {
            leaf arg {
                type string;
            }

            leaf arg2 {
                type int8;
            }
        }

        output {
            leaf ret {
                type int64;
            }
        }
    }

    notification notif {
        leaf val {
            type decimal64 {
                fraction-digits 2;
            }
        }
    }
}
